# ch02_SystemRequirements

## SR-001: Equation 1 Calculation (Container)
The system shall generate output y according to:
y = (t^2) - 4(t) + 21
- Rationale: <<NULL>>

### #2: Interface Requirements (Container)
<<NULL>>
- Rationale: <<NULL>>

#### IR-001: Time Input (Informational)
The system shall accept time t as an input represented in seconds.
- Rationale: <<NULL>>

#### IR-002: Y Output (Informational)
The system shall provide y as an output.
- Rationale: <<NULL>>

### #5: Functional Requirements (Container)
<<NULL>>
- Rationale: <<NULL>>

#### FR-001: Calculate Y (Functional)
The system shall calculate:
y = (t^2) - 4(t) + 21
- Rationale: <<NULL>>

### #7: Initial Conditions (Container)
<<NULL>>
- Rationale: <<NULL>>

#### IC-001: Initialize Time (Functional)
At initialization, t shall equal 0.0 seconds.
- Rationale: <<NULL>>

#### IC-002: Initialize Y (Functional)
At initialization, y shall equal 0.0.
- Rationale: <<NULL>>
