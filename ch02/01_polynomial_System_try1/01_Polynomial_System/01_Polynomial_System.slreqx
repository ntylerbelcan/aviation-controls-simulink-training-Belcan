# 01_Polynomial_System
The software shall establish known initial values for all variables associated with Equation 1 at startup.

## SR-001: Software Requirements (Container)
<<NULL>>
- Rationale: <<NULL>>

### HLR-001: Generate Time Signal (Functional)
The software shall generate a time signal from 0.0 s to 15.0 s in increments of 0.25 sec.
- Rationale: <<NULL>>

### HLR-002: Compute Polynomial (Functional)
The software shall compute:
y = COEFF_A*(t^2) + COEFF_B*(t) + COEFF_C
where:
COEFF_A = 1
COEFF_B = -4
COEFF_C = 21
- Rationale: <<NULL>>

### HLR-003: Store Y as Float (Functional)
The software shall store y as a floating-point value.
- Rationale: <<NULL>>

### HLR-004: Output Y (Functional)
The software shall provide y at the output interface.
- Rationale: <<NULL>>

## #6: Initial Conditions (Container)
<<NULL>>
- Rationale: <<NULL>>

### HLR-005: Initialize Time Signal (Functional)
The software shall initialize the time value to 0.0 seconds at startup.
- Rationale: <<NULL>>

### HLR-006: Initialize Y Output (Functional)
The software shall initialize y to 0.0 at startup.
- Rationale: <<NULL>>
